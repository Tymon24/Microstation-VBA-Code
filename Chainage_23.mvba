Attribute VB_Name = "Chainage"
Option Explicit
Option Base 0

'initiate chainage app
Sub AddChainage()
    UserForm.Show

End Sub

Attribute VB_Name = "Routines_Level"
'-------------------------------------------------------------------
'Module:        Modules to manipulate level information
'Description:
'By:            Tymon Mellor
'Contact:       tymon.mellor@gmail.com
'Date:          20 May 2020
'Notes:
'Revision:      1.0
'-------------------------------------------------------------------

'set explicit on
Option Explicit

'set array base
Option Base 0

'-------------------------------------------------------------------
'Module:        SetLevel
'Description:   Routine to create/set a level and override information
'By:            Tymon Mellor
'Contact:       tymon.mellor@gmail.com
'Date:          20 May 2020
'Notes:         Requires
'               sLevelName As String - level name
'               nColour As Integer - over ride colour
'               nStyle As Integer - over ride line style
'               nWeight As Integer - over ride line weight
'Revision:      1.0
'-------------------------------------------------------------------

Sub SetLevel(sLevelName As String, nColour As Integer, nStyle As Integer, nWeight As Integer)
    Dim oLevel          As Level
    Dim oLevelList      As Levels
    Dim oStyle          As LineStyle
    
    'nStyle need to add 1 to maintain range
    nStyle = nStyle + 1
    
    'save current levels
    Set oLevelList = ActiveDesignFile.Levels
    
    'see if level defined
    Set oLevel = oLevelList.Find(sLevelName)
    
    'check level name against defined
    If oLevel Is Nothing Then
        'add new level
        Set oLevel = ActiveDesignFile.AddNewLevel(sLevelName)
        oLevelList.Rewrite
        MsgBox "Created new level '" & sLevelName & "'", vbInformation Or vbOKOnly, "Level Created"
    End If

    'set override details
    oLevel.OverrideColor = nColour
    oLevel.OverrideLineWeight = nWeight

    'style needs an object
    Set oStyle = ActiveDesignFile.LineStyles.Item(nStyle)
    
    'check if valid style
    If oStyle Is Nothing Then
        MsgBox "Invalid line style '" & CStr(nStyle) & "'", vbExclamation Or vbOKOnly, "Invalid Line Style"
        Else
        Set oLevel.OverrideLineStyle = oStyle
    End If
    
End Sub

Attribute VB_Name = "Routines_Plot"
'-------------------------------------------------------------------
'Module:        Modules to plot lines and text
'Description:
'By:            Tymon Mellor
'Contact:       tymon.mellor@gmail.com
'Date:          20 May 2020
'Notes:
'Revision:      1.0
'-------------------------------------------------------------------

'set explicit on
Option Explicit

'set array base
Option Base 0


'-------------------------------------------------------------------
'Module:        PlotLine
'Description:   Routine to plot a straight line
'By:            Tymon Mellor
'Contact:       tymon.mellor@gmail.com
'Date:          20 May 2020
'Notes:         Requires
'               sLevelName As String - level name
'               oPoints() As Point3d - multiple points
'Revision:      1.0
'-------------------------------------------------------------------
Sub PlotLine(sLevelName As String, oPoints() As Point3d)
    Dim oLine           As Element
    Dim oLevel          As Level
    Dim nInt            As Integer
    Dim oPlot()         As Point3d
    
    'redim plotting array - used to avoid changes to data
    ReDim oPlot(UBound(oPoints))
    
    'check level name exists,
    Set oLevel = ActiveDesignFile.Levels.Find(Trim(sLevelName))
       
    'check level name against defined
    If oLevel Is Nothing Then
        MsgBox "Level '" & sLevelName & "' not defined"
        Exit Sub
    End If
    
    'adjust for defined start
    For nInt = 0 To UBound(oPoints)
        oPlot(nInt).X = oPoints(nInt).X
        oPlot(nInt).Y = oPoints(nInt).Y
        oPlot(nInt).Z = oPoints(nInt).Z
    Next
    
    'create the shape element
    Set oLine = CreateLineElement1(Nothing, oPlot)
   
    'set the level
    Set oLine.Level = ActiveDesignFile.Levels(sLevelName)
    
    'draw the element
    ActiveModelReference.AddElement oLine
    
    oLine.Redraw
    
End Sub


'-------------------------------------------------------------------
'Module:        PlotText
'Description:   Routine to plot texts at defined angle and justification
'By:            Tymon Mellor
'Contact:       tymon.mellor@gmail.com
'Date:          20 May 2020
'Notes:         Requires
'               sLevelName As String - level name
'               oPoint As Point3d - single point
'               sText As String - text to plot
'               nAngle As Double - plot angle in degrees
'               nSize as Single - text size
'               Optional nJust As Integer = 0 - justification default msdTextJustificationLeftTop
'               Text size and weight defined as constants
'Revision:      1.0
'-------------------------------------------------------------------



'plot text note nAngle in degree
Sub PlotText(sLevelName As String, oPoint As Point3d, sText As String, nAngle As Double, nSize As Double, Optional nJust As Integer = 0)
    Dim oLevel          As Level
    Dim oTextElement    As TextElement
    Dim oRotation       As Matrix3d
    
    'check level name exists,
    Set oLevel = ActiveDesignFile.Levels.Find(Trim(sLevelName))
       
    'check level name against defined
    If oLevel Is Nothing Then
        MsgBox "Level '" & sLevelName & "' not defined"
        
        'set level
        SetLevel sLevelName, 1, 3, 1
'        Exit Sub
    End If
           
    'create the shape element
    Set oTextElement = CreateTextElement1(Nothing, sText, oPoint, oRotation)
   
    'set the level
    Set oTextElement.Level = ActiveDesignFile.Levels(sLevelName)
        
    'set style
    oTextElement.LineWeight = 1
    oTextElement.TextStyle.Height = nSize
    oTextElement.TextStyle.Width = nSize
    oTextElement.TextStyle.Direction = msdTextDirectionHorizontal
    oTextElement.TextStyle.Justification = nJust
    oTextElement.TextStyle.Color = 0
       
    'convert nAngle to radians
    If nAngle > 0 Then
        nAngle = nAngle / 180 * Pi()
    End If
    
    'rotate text
    oTextElement.Rotate oPoint, 0, 0, nAngle
    
    'draw the element
    ActiveModelReference.AddElement oTextElement
    
    oTextElement.Redraw


End Sub

Attribute VB_Name = "UserForm"
Attribute VB_Base = "0{173755ED-2860-4325-A11D-E033AD6E72AF}{C0785FCE-EE5D-443F-A1B3-B59E286554D5}"
Attribute VB_GlobalNameSpace = False
Attribute VB_Creatable = False
Attribute VB_PredeclaredId = True
Attribute VB_Exposed = False
Attribute VB_TemplateDerived = False
Attribute VB_Customizable = False
'-------------------------------------------------------------------
'Module:        Main Form for Chainage application code
'Description:   VBA to add chainage to complex chain
'By:            Tymon Mellor
'Contact:       tymon.mellor@gmail.com
'Date:          8 Sept 2018
'Notes:         Adds chainage markers to a selected complex chain
'Revision:      1.0
'               1.1 19 May 2020
'               1.2 20 May 2020
'               1.3 15 Sep 2023 Sorted out level on line
'               1.4 20 Sep 2023 Sorted out vertical lines and chainage
'-------------------------------------------------------------------

'set explicit on
Option Explicit

'set array base
Option Base 0


'Initiat form and check line selected
Sub UserForm_Initialize()
    Dim oElementList    As ElementEnumerator
       
    'check to see something selected
    Set oElementList = ActiveModelReference.GetSelectedElements
    
    'check element selected
    If Not oElementList.MoveNext Then
        MsgBox "Please select line or complex chain to add chainage", vbCritical, "Chainage Line"
        'stop the application
        End
    End If
     
    tbMajor = 100
    tbMinor = 10
     
End Sub

'close form
Private Sub cbCancel_Click()
    'close form
    Unload Me
End Sub

'main code to add the details
Private Sub cbOK_Click()
    Dim oElementList    As ElementEnumerator
    Dim oElement        As Element
    Dim nLine           As Integer
     
    'save selected elements
    Set oElementList = ActiveModelReference.GetSelectedElements
    
    'check for multiple element selected
    If oElementList.MoveNext Then
        'save the cutting element
        Set oElement = oElementList.Current
        
        'check if more than one element
        If oElementList.MoveNext Then
            MsgBox "Only select one chainage element", vbCritical, "Add Chainage"
            Exit Sub
        End If
        
    End If
        
    
    'check selected element is chainagable
    If Not oElement.IsChainableElement Then
        MsgBox "Selected element is not a line or complex chain, select a continuous element", vbCritical, "Add Chainage"
        Exit Sub
    End If
      
    'ensure object is left to right
    If oElement.AsChainableElement.StartPoint.X > oElement.AsChainableElement.EndPoint.X Then
        oElement.AsChainableElement.Reverse
    End If
       
     
    'define line type 0 = cross -1 = South 1 = North
    If opNorth.Value = True Then nLine = 1
    If opCross.Value = True Then nLine = 0
    If opSouth.Value = True Then nLine = -1
   
    'correct east to west
    If ob_EastWest.Value Then
        'run chainage in reverse
        oElement.AsChainableElement.Reverse
        
        'swap the line side
        nLine = nLine * -1
        
    End If
'----------------------------------------------
    'draw chainage marks, spacing, length and side
    CrossingPerpendiculars oElement, tbMinor, tbMinor * 0.5, nLine
'----------------------------------------------
   
    'completion message
'    MsgBox "Run Complete", vbInformation, "Add Chainage"
    
    'close the form
    cbCancel_Click
    
End Sub


'-------------------------------------------------------------------
'Module:        CrossingPerpendiculars
'Description:   Routine to draw perpendicular lines along an element
'By:            Tymon Mellor
'Contact:       tymon.mellor@gmail.com
'Date:          20 May 2020
'Notes:         LinearElem As Element - element to chain
'               nInterval As Long - interval between lines
'               Distance As Double - length of marking line
'               Optional Side As Integer = 0 - 0 means cross, 1 means left, -1 means right
'Source:        https://communities.bentley.com/products/programming/microstation_programming/f/archived-microstation-v8-xm-edition-vba-forum/20356/perpendicular-lines-to-complexstringelement-or-chainableelement
'Revision:      1.0
'-------------------------------------------------------------------
Sub CrossingPerpendiculars(LinearElem As Element, nInterval As Long, Distance As Double, Optional Side As Integer = 0)
    Dim bSpl As BsplineCurve
    Set bSpl = New BsplineCurve

    Dim FrenetFrame As Matrix3d, Param As Double, Curvature As Double, Torsion As Double
    Dim Tangent As Point3d, Normal As Point3d, BiNormal As Point3d
    Dim LinearNormal As Point3d: LinearNormal = Point3dFromXYZ(0, 1, 0)
    Dim StartPoint As Point3d, EndPoint As Point3d, Length As Double
    Dim oLine As LineElement
    Dim halfDist As Double: halfDist = Distance * 0.5
    Dim oLevel As Level
    Dim nAngle As Double
    Dim nAngle2 As Double
    Dim nTextJust As Integer
    Dim sLName As String
    Dim oView As View
    Dim nStart As Double

    'set level name for chainage details
    sLName = "tm_chain"
    

    'confirm traversable element
    If LinearElem.IsTraversableElement Then
        
        'check level name exists,
        Set oLevel = ActiveDesignFile.Levels.Find(Trim(sLName))
       
        'check level name against defined
        If oLevel Is Nothing Then
            MsgBox "Level '" & sLName & "' not defined"
        
            'set level
            SetLevel sLName, 1, 3, 1
    '        Exit Sub
        End If
        
        
        'create bspline curve
        bSpl.FromElement LinearElem
        
        'establish curve length
        Length = bSpl.ComputeCurveLength

        'set through intervals
        For Length = 0 To Length Step nInterval
            
            'locate point
            bSpl.EvaluatePointAtDistance Param, Length
            
            'establish point on the curve
            StartPoint = bSpl.EvaluatePointFrame(FrenetFrame, Curvature, Torsion, Param, LinearNormal)

            ' If UpVector is 0, 0, 1, then we know, that if Frenets UpVector's Z value is less than zero,
            ' it is up side down for us... So we can negate it's needed rows...

            If FrenetFrame.RowZ.Z < 0 Then
                ' RowZ [Binormal/UpVector in 2D] is not needed negated now, so we can keep it unchanged
                'FrenetFrame.RowZ = Point3dNegate(FrenetFrame.RowZ)

                ' RowY [Normal/SideVector in 2D] is only needed on correct side
                FrenetFrame.RowY = Point3dNegate(FrenetFrame.RowY)

                ' RowX [Tangent/DirectionVector] is not needed negated now too...
                'FrenetFrame.RowX = Point3dNegate(FrenetFrame.RowX)
            End If

            'establish which side of the line
            If Side = 0 Then

                EndPoint = Point3dAddScaled(StartPoint, FrenetFrame.RowY, halfDist)
                StartPoint = Point3dAddScaled(StartPoint, FrenetFrame.RowY, -halfDist)

                Else

                EndPoint = Point3dAddScaled(StartPoint, FrenetFrame.RowY, Side * Distance)
                          
            End If

            'for vertical line
            If StartPoint.X = EndPoint.X And StartPoint.Y = EndPoint.Y Then
                EndPoint.X = StartPoint.X - Side * Distance
            End If

      '      Debug.Print StartPoint.X, EndPoint.X

            Set oLine = CreateLineElement2(Nothing, StartPoint, EndPoint)
            
            'set the level
            Set oLine.Level = ActiveDesignFile.Levels(sLName)
    
            
            ActiveModelReference.AddElement oLine
            oLine.Redraw
     
     
            
      '      Debug.Print Length, (Length + tb_Start.Value) Mod tbMajor
            'add the original chainage
            'check if major interval but make sure its divisible
            nStart = tb_Start.Value '- tb_Start.Value Mod tbMinor
            
            If (Length + nStart) Mod tbMajor = 0 Then
                
                'new approach to avoid division by zero
                Set oView = ActiveDesignFile.Views(1)
                
                'get the angle in degrees
                nAngle2 = GetActiveAngleFrom2Points(StartPoint, EndPoint, oView) + 180
                
                'check for vertical line
                If nAngle2 = 180 Then
                    nAngle2 = nAngle2 - 180
                End If
                
                
                'angle of line in radians
          '      nAngle = Atn((StartPoint.X - EndPoint.X) / (StartPoint.Y - EndPoint.Y))
        
                'set text angle
          '      nAngle = 270 - nAngle * 180 / Pi()
                
          '      Debug.Print StartPoint.X, EndPoint.X, nAngle2
                
                nAngle = nAngle2
                                
                'adjust start for the site west to east
                If Side = -1 Then   '-1 south side
                    nTextJust = msdTextJustificationLeftTop
                    Else
                    'side = 1 north and 0 cross
                    nTextJust = msdTextJustificationRightTop
                End If
            
                'east to west
                If ob_EastWest.Value Then
                
                    'adjust start for the site west to east
                    If Side = -1 Then   '-1 south side
                        nTextJust = msdTextJustificationRightTop
                        Else
                        'side = 1 north and 0 cross
                        nTextJust = msdTextJustificationLeftTop
                    End If
                End If
            
                PlotText sLName, EndPoint, Format(Length + nStart, "0+000"), nAngle, tbMinor * 0.3, nTextJust
                
            End If

        Next Length
        
        Else
        
        Debug.Print "Element is not traversable!!!"
    
    End If

End Sub


'Return same angle as keyin "active angle pt2"
Function GetActiveAngleFrom2Points(pt1 As Point3d, pt2 As Point3d, oView As View) As Double
    Dim vec1 As Vector3d, vec2 As Vector3d
    Dim angle As Double
    
    'get vectors in plane of view
    vec1 = Vector3dFromMatrix3dTimesVector3d(oView.Rotation, Vector3dSubtractPoint3dPoint3d(pt2, pt1))
    vec2 = Vector3dFromXY(1#, 0#)
    
    'duplicate keyin logic
    angle = Degrees(Vector3dAngleBetweenVectorsXY(vec2, vec1))
    If angle < 0# Then
        angle = angle + 360#
    End If
    
    GetActiveAngleFrom2Points = angle
End Function
